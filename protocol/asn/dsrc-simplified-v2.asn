-- ~~~~~~~~~~~~~~~~~~~~~~~~~~~~~~~~~~~~~~~~~~~~~~~~~~~~~~~~~~~~~~~~~~~~~~~~~~~~~~~~~~~~
-- ISO TS 19091
--
-- This document contains the data element needed for the encoding the CPM
--
-- ~~~~~~~~~~~~~~~~~~~~~~~~~~~~~~~~~~~~~~~~~~~~~~~~~~~~~~~~~~~~~~~~~~~~~~~~~~~~~~~~~~~~

-- ^-^-^-^-^-^-^-^-^-^-^-^-^-^-^-^-^-^-^-^-^-^-^-^-^-^-^-^-
--
-- module: DSRC
--
-- ^-^-^-^-^-^-^-^-^-^-^-^-^-^-^-^-^-^-^-^-^-^-^-^-^-^-^-^-
DSRC {
    iso(1) standard(0) signalizedIntersection(19091) profilec(2) dsrc(2) version2(2)
}
DEFINITIONS AUTOMATIC TAGS ::=
BEGIN

IMPORTS
    Longitude,
    Latitude
FROM ITS-Container {
    itu-t(0) identified-organization(4) etsi(0) itsDomain(5) wg1(1) ts(102894) cdd(2) version(2)
};


IntersectionReferenceID ::= SEQUENCE {
   region  RoadRegulatorID OPTIONAL,
   id      IntersectionID
}

IntersectionID ::= INTEGER (0..65535)

Offset-B10 ::= INTEGER (-512..511)

Offset-B11 ::= INTEGER (-1024..1023)

Offset-B12 ::= INTEGER (-2048..2047)

Offset-B13 ::= INTEGER (-4096..4095)

Offset-B14 ::= INTEGER (-8192..8191)

Offset-B16 ::= INTEGER (-32768..32767)

LaneID ::= INTEGER (0..255)

NodeOffsetPointXY ::= CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
-- asn1rs type replcaement because class types are not supported
--        This doesn't matter here because it is marked as always absent in CPM-PDU-Descriptions:312
--   regional         RegionalExtension {{Reg-NodeOffsetPointXY}}
   regional         NULL            -- node which follows is of a regional definition type
}

Node-LLmD-64b ::= SEQUENCE {
   lon  Longitude,
   lat  Latitude
}

Node-XY-20b ::= SEQUENCE {
   x  Offset-B10,
   y  Offset-B10
}

Node-XY-22b ::= SEQUENCE {
   x  Offset-B11,
   y  Offset-B11
}

Node-XY-24b ::= SEQUENCE {
   x  Offset-B12,
   y  Offset-B12
}

Node-XY-26b ::= SEQUENCE {
   x  Offset-B13,
   y  Offset-B13
}

Node-XY-28b ::= SEQUENCE {
   x  Offset-B14,
   y  Offset-B14
}

Node-XY-32b ::= SEQUENCE {
   x  Offset-B16,
   y  Offset-B16
}

-- asn1rs does not support class types
-- REG-EXT-ID-AND-TYPE ::= CLASS {
--   &id     RegionId UNIQUE,
--   &Type
-- } WITH SYNTAX {&Type IDENTIFIED BY &id}

RegionId ::= INTEGER (0..255)
   noRegion     RegionId ::= 0  -- Use default supplied stubs
   addGrpA      RegionId ::= 1  -- USA
   addGrpB      RegionId ::= 2  -- Japan
   addGrpC      RegionId ::= 3  -- EU
   -- NOTE: new registered regional IDs will be added here
   -- The values 128 and above are for local region use

-- asn1rs does not support class types
-- RegionalExtension {REG-EXT-ID-AND-TYPE : Set} ::= SEQUENCE {
--   regionId     REG-EXT-ID-AND-TYPE.&id( {Set} ),
--   regExtValue  REG-EXT-ID-AND-TYPE.&Type( {Set}{@regionId} )
-- }


RoadSegmentReferenceID ::= SEQUENCE {
   region  RoadRegulatorID OPTIONAL,
   id      RoadSegmentID
}

RoadRegulatorID ::= INTEGER (0..65535)

RoadSegmentID ::= INTEGER (0..65535)

VehicleHeight ::= INTEGER (0..127)

END
