DENM-PDU-Descriptions {
    itu-t(0) identified-organization(4) etsi(0) itsDomain(5) wg1(1) en(302637) denm(1) version(2) 
} 
DEFINITIONS AUTOMATIC TAGS ::= 
BEGIN 
IMPORTS  
    ItsPduHeader, CauseCode, Speed, InformationQuality, ReferencePosition, ClosedLanes,
    DangerousGoodsExtended, Heading, LanePosition, LightBarSirenInUse, RoadType, HeightLonCarr,
    PosLonCarr, PosCentMass, PositioningSolutionType, RequestResponseIndication, StationType, SpeedLimit,
    StationarySince, TimestampIts, WheelBaseVehicle, TurningRadius, PosFrontAx, PositionOfOccupants,
    Temperature, VehicleMass, VehicleIdentification, EnergyStorageType, ActionID, ItineraryPath,
    NumberOfOccupants, PositionOfPillars, RelevanceTrafficDirection, RestrictedTypes, Traces,
    TransmissionInterval, ValidityDuration, RelevanceDistance, EventHistory, TrafficRule,
    DeltaReferencePosition
FROM ITS-Container {
    itu-t(0) identified-organization(4) etsi(0) itsDomain(5) wg1(1) ts(102894) cdd(2) version(2)
};

DENM ::= SEQUENCE {

     ---  The ITS PDU header of a DENM. This DF includes the protocol version
     ---  of the DENM protocolVersion, DENM message type identifier messageID
     ---  and station identifier stationID of the originating ITS-S or ITS-S
     ---  that optionally forwards the DENM.
     ---  The DE protocolVersion is used to select the appropriate protocol
     ---  decoder at the receiving ITS-S. For the present standard, the value
     ---  of the DE protocolVersion shall be set to 1, the DE messageID shall
     ---  be set to 1. For the originating ITS-S, the stationID shall be set to
     ---  the station ID of the originating ITS-S. For the forwarding ITS-S,
     ---  the stationID shall be set to the station ID of the forwarding ITS-S,
     ---  if the DENM is forwarded. This DF shall be presented as specified in
     ---  ETSI TS 102 894-2 [5] ItsPduHeader.
     header  ItsPduHeader,
     
     ---  DENM payload. It includes the mandatory container management
     ---  container and optional containers situation container, location
     ---  container and alacarte container.
     denm    DecentralizedEnvironmentalNotificationMessage    
} 

DecentralizedEnvironmentalNotificationMessage ::= SEQUENCE {

     ---  Management container of a DENM as described in clause 7.1.3. It
     ---  contains information required for the DENM protocol processing.
     management ManagementContainer,
     
     ---  Situation container of a DENM as described in clause 7.1.4. It
     ---  contains information of the event type and event detection quality.
     situation  SituationContainer  OPTIONAL,
     
     ---  Location container of a DENM as described in clause 7.1.5. It
     ---  contains information of the location referencing. This DF is
     ---  optional. It shall not be present in cancellation DENM and negation
     ---  DENM.   
     location   LocationContainer   OPTIONAL,
     
     ---  À la carte container of a DENM as described in clause 7.1.6. It
     ---  contains use case specific information that has not been provided in
     ---  other DENM containers.
     ---  This DF is optional. It shall not be present in cancellation DENM and
     ---  negation DENM. It shall be present in a new DENM or update DENM, if
     ---  the information is required by the ITS application. 
     alacarte   AlacarteContainer   OPTIONAL 
}

ManagementContainer ::= SEQUENCE {
    
    --- Identifier generated by the DEN basic service for new DENM. The
    --- actionID differs from the actionIDs generated by other ITS-Ss and from
    --- the actionIDs generated by the same ITS-S for other detected events. It
    --- is used by a receiving ITS-S to process information for DENMs that are
    --- multiply received. The actionID is maintained by the originating ITS-S.
    ---
    --- The data setting rules of actionID are as specified in clause 8.2.1.2.
    --- This DF is composed of an ITS-S identifier and a sequence number. The
    --- ITS-S ID describes the station ID of the originating ITS-S that
    --- generates a new DENM. The sequence number is set each time a new DENM
    --- is created. It is used to differentiate from events detected by the
    --- same ITS-S. This DF shall be presented as specified in
    --- ETSI TS 102 894-2 [5] 
    actionID                   ActionID,

    --- Time at which the event is detected by the originating ITS-S. For the
    --- DENM repetition, this DE shall remain unchanged. For the DENM update,
    --- this DE shall be the time at which the event update is detected. For
    --- the DENM termination, this DE shall be the time at which the
    --- termination of the event is detected.   
    --- This DE shall be presented as specified in ETSI TS 102 894-2 [5]
    --- TimestampIts.
    detectionTime              TimestampIts,

    --- This DE refers to the time at which a new DENM, an update DENM or a
    --- cancellation DENM is generated.   This DE is maintained by the DEN
    --- basic service of the originating ITS-S.
    --- The referenceTime is maintained by the originating ITS-S, the data
    --- setting rules are as specified in clause 8.2.1.3. This DE shall be
    --- presented as specified in ETSI TS 102 894-2 [5] TimestampIts. 
    referenceTime              TimestampIts,

    --- This DE indicates if the type of generated DENM is a cancellation DENM
    --- or a negation DENM.   The termination is maintained by the originating
    --- ITS-S. 
    --- This DE is OPTIONAL. It shall be present if the generated DENM is a
    --- cancellation DENM or negation DENM. The data setting rules of this DE
    --- is as specified in clause 8.2.1.4. This DE shall be presented as
    --- specified in Annex A.
    termination                Termination                 OPTIONAL,

    --- Geographical position of the detected event. The position of an event
    --- is determined by the originating ITS-S.
    --- When the event position corresponds to the position of a vehicle ITS-S,
    --- the eventPosition shall be set to the position of the vehicle ITS-S at
    --- detectionTime. This DF shall be presented as specified in
    --- ETSI TS 102 894-2 [5] ReferencePosition
    eventPosition              ReferencePosition,

    --- The distance in which event information is relevant for the receiving
    --- ITS-S, starting from the event position as defined in clause 6.1.3.1.
    --- This DE is OPTIONAL. It shall be present when the information is
    --- required by the ITS application.   This DE shall be presented as
    --- specified in ETSI TS 102 894-2 [5] RelevanceDistance.
    relevanceDistance          RelevanceDistance           OPTIONAL,

    --- The traffic direction along which the event information is relevant
    --- for the receiving ITS-S, as defined in clause 6.1.3.1
    --- This DE is OPTIONAL. It shall be present when the information is
    --- required by the ITS application.   This DE shall be as presented as
    --- specified in ETSI TS 102 894-2 [5] RelevanceTrafficDirection.
    relevanceTrafficDirection  RelevanceTrafficDirection   OPTIONAL,

    --- Validity duration of a DENM. The validityDuration is set by the
    --- originating ITS-S. Therefore it represents an estimation of how long
    --- the event may persist. It implies the duration over which the DENM
    --- should be kept at the DEN basic service of the receiving ITS-S and the
    --- DENM dissemination be maintained in the relevance area or destination
    --- area, until the expiration of validityDuration. In case the expiry time
    --- of the event cannot be estimated at the originating ITS-S, a default
    --- value is used for the DENM protocol operation. This DE may be renewed
    --- by the originating ITS-S, if the pre-set expiry time has reached to its
    --- limit and the originating ITS-S detects that the event persists.
    --- 
    --- The DE is represented as a time offset in the unit of second since
    --- detectionTime. This DE is optional. It shall be present if the
    --- information is required by the ITS application. If the DE is not
    --- present in DENM, a default value defaultValidity is assumed. This DE
    --- shall be presented as specified in ETSI TS 102 894-2 [5]
    --- ValidityDuration.
    validityDuration           ValidityDuration            DEFAULT defaultValidity,

    --- Time interval for DENM transmission as defined by the originating
    --- ITS-S. This DE informs the receiving ITS-Ss about the intended
    --- transmission interval of two consecutive DENM transmissions. It is used
    --- for the forwarding ITS-S operation.
    --- This DE is optional. If the ITS-S application of the originating ITS-S
    --- does not provide this information to the DEN basic service, the DE
    --- shall not be included in DENM. In this case, the DENM shall not be
    --- forwarded by the forwarding ITS-S. This DE shall be presented as
    --- specified ETSI TS 102 894-2 [5] TransmissionInterval.
    transmissionInterval       TransmissionInterval        OPTIONAL,

    --- This DE provides the station type information of the originating ITS-S.
    --- This DE shall be presented as specified in ETSI TS 102 894-2 [5]
    --- StationType.
    stationType                StationType,
    
    ...
}

SituationContainer ::= SEQUENCE {

    --- Quality level of the information provided by the ITS-S application of
    --- the originating ITS-S. It indicates the probability of the detected
    --- event being truly existent at the event position.
    --- This DE is set according to the ITS application requirements. If the
    --- information is unknown, the DE shall be set to 0. This DE shall be
    --- presented as specified in ETSI TS 102 894-2 [5] InformationQuality.
    informationQuality  InformationQuality,

    --- Description for the event type, including direct cause and sub cause.
    --- The assignment of the event cause codes is based on TISA TAWG11071
    --- [i.10] and the specification in Table 10 in clause 7.1.4 of the present
    --- document.
    --- This DF shall be presented as specified in ETSI TS 102 894-2 [5]
    --- CauseCode.
    eventType           CauseCode,

    --- Description for a linked event of the provided eventType, including
    --- direct cause and sub cause of the linked event. The assignment of the
    --- linkedCause is based on TISA TAWG11071 [i.10] and the specification in
    --- Table 10 in clause 7.1.4 of the present document.
    --- This DF is OPTIONAL. It shall be present if the information is provided
    --- by the ITS-S application of the originating ITS-S. This DF shall be
    --- presented as specified in ETSI TS 102 894-2 [5] CauseCode. 
    linkedCause         CauseCode       OPTIONAL,

    --- The DF consists of a list of event points which represents the
    --- dimension of a plain event in a predefined order. In case that the
    --- plain event is detected by a vehicle ITS-S, the DF consists of a list
    --- of event detection points along the path that the detecting ITS-S has
    --- travelled over some past time and/or distance. Each event point
    --- corresponds to a point at which the same event was detected along the
    --- path. In the present document up to 40 EventPoint may be added in this
    --- DF. The generation of each EventPoint is specified in the related ITS
    --- application requirements.
    --- The EventPoint closest to the current detected event point with respect
    --- to the detectionTime or eventPosition shall be put as the first point.
    --- It represents an offset delta position and optionally an offset delta
    --- detection time with regards to the current detected event point. The
    --- delta detection time may not be present, in case the detecting plain
    --- event is pre-defined by the detecting ITS-S, e.g. a roadwork zone
    --- covering a certain distance along the road. Other event points shall be
    --- structured in ascending order according to the detectionTime or
    --- eventPosition. Each event point represents an offset delta position
    --- with respect to the previous EventPoint. This DF is OPTIONAL, it shall
    --- be present if required by the ITS application. This DF shall be
    --- presented as specified in ETSI TS 102 894-2 [5] EventHistory.    
    eventHistory        EventHistory    OPTIONAL,
    
    ...

}

LocationContainer ::= SEQUENCE {

    --- Moving speed of a detected event and the confidence of the moving speed
    --- information. If not specified elsewhere, 95 % confidence interval shall
    --- apply to this DF. An ITS application may require specific confidence
    --- interval.
    --- When the eventPosition corresponds to the position of a vehicle ITS-S,
    --- the eventSpeed shall be set to the vehicle speedat detectionTime. This
    --- DF is OPTIONAL. It shall be present if this information is required by
    --- the ITS application. This DF shall be presented as specified in
    --- ETSI TS 102 894-2 [5] Speed.
    eventSpeed             Speed       OPTIONAL,     

    --- The heading direction of the event and the confidence of the heading
    --- information, if applicable. If not specified elsewhere, 95 % confidence
    --- interval shall apply to this DF. An ITS application may require
    --- specific confidence interval.
    --- This DF is OPTIONAL. It shall be present when this information is
    --- required by the ITS application. This DF shall be as presented as
    --- specified in ETSI TS 102 894-2 [5] Heading. 
    eventPositionHeading   Heading     OPTIONAL,     

    --- This DF is the location referencing information of eventPosition. It
    --- includes a group of traces as defined in clause 6.1.3.2.Each trace
    --- describes a set of consecutive PathPoint positions leading to the event
    --- position. ITS-Ss located near to or inside this trace path may be
    --- concerned by the event. Multiple traces may be defined in case multiple
    --- road sections or traffic flows are leading to the event position. In
    --- the present standards, up to seven traces may be added in a DENM. For
    --- each trace, multiple PathPoint positions are provided to describe the
    --- trace path.
    --- Within one trace, the PathPoint closest to the event position shall be
    --- put as the first waypoint, itpresents an offset delta position with
    --- regards to the eventPosition. Other PathPoints shall be structured in
    --- ascending order according to the distance to the eventPosition along
    --- the trace path. Each PathPoint presents an offset delta position and
    --- optionally an offset travel time with regards to the previous
    --- PathPoint. The DE PathDeltaTime as defined in PathPoint in
    --- ETSI TS 102 894-2 [5] is OPTIONAL, it shall be present if the
    --- information is required by the ITS application. When the event position
    --- corresponds to the position of a vehicle ITS-S, the first trace in the
    --- DF shall be the PathHistory of the vehicle as defined in the CA basic
    --- service ETSI EN 302 637 – 2 7. The traces shall be presented as
    --- specified as in ETSI TS 102 894-2 [5] Traces. Each trace shall be
    --- presented as specified in ETSI TS 102 894-2 [5] PathHistory.
    traces                 Traces,

    --- The road type information at the event position.
    --- This DE is OPTIONAL. It shall be present when this information is
    --- required by the ITS application.   This DE shall be presented as
    --- specified in ETSI TS 102 894-2 [5] RoadType.
    roadType               RoadType    OPTIONAL,

    ...   

}

ImpactReductionContainer ::= SEQUENCE {

    --- Height of left longitudinal carrier of the vehicle from base to top.
    --- The left carrier refers to the left side seen from vehicle rear to
    --- vehicle front. This DE is included in the impactReduction DF.
    --- This DE shall be presented as specified in ETSI TS 102 894-2 [5]
    --- HeightLonCarr.
    heightLonCarrLeft          HeightLonCarr,

    --- Height of right longitudinal carrier of the vehicle from base to top.
    --- The right carrier refers to the right side seen from vehicle rear to
    --- vehicle front. This DE is included in the impactReduction DF.
    --- This DE shall be presented as specified in ETSI TS 102 894-2 [5]
    --- HeightLonCarr.
    heightLonCarrRight         HeightLonCarr,

    --- Distance from the centre of vehicle front bumper to the front of the
    --- left longitudinal carrier of vehicle. The left carrier refers to the
    --- left seen from vehicle rear to vehicle front. This DE is included in
    --- the impactReduction DF.
    --- This DE shall be presented as specified in ETSI TS 102 894-2 [5]
    --- PosLonCarr.
    posLonCarrLeft             PosLonCarr,

    --- Longitudinal distance from the centre of vehicle front bumper to the
    --- front of right longitudinal carrier of vehicle. The right carrier
    --- refers to the right side seen from vehicle rear to vehicle front. This
    --- DE is included in the impactReduction DF.
    --- This DE shall be presented as specified in ETSI TS 102 894-2 [5]
    --- PosLonCarr.
    posLonCarrRight            PosLonCarr,

    --- The positionOfPillars contains a list of distance, which refers to the
    --- perpendicular distance between centre of vehicle front bumper to
    --- vehicle A pillar, between neighbour vehicle pillars until the last
    --- pillar of the vehicle.   This DF is included in the impactReduction DF.
    --- This DF is defined for passenger vehicles only.
    --- This DF shall be presented as specified in ETSI TS 102 894-2 [5]
    --- PositionOfPillars. Each pilliar distance shall be presented as
    --- specified in ETSI TS 102 894-2 [5] PosPillar.
    positionOfPillars          PositionOfPillars,

    --- Perpendicular distance from centre of mass of an empty charged vehicle
    --- to vehicle front bumper. This DE is included in the impactReduction DF.
    --- This DE shall be presented as specified in ETSI TS 102 894-2 [5] PosCentMass.
    posCentMass                PosCentMass,

    --- Perpendicular distance between front and rear axle of the wheel base of
    --- a passenger vehicle.   This DE is included in the impactReduction DF in
    --- the alacarte container.
    --- This DE shall be presented as specified in ETSI TS 102 894-2 [5]
    --- WheelBaseVehicle.
    wheelBaseVehicle           WheelBaseVehicle,

    --- The turning radius of a vehicle is the size of the smallest circular
    --- turn (i.e. U-turn) that the vehicle is capable of making. This DE is
    --- included in the impactReduction DF in the alacarte container. When a
    --- trailer is present, this DE shall provide the turning radius of the
    --- vehicle.
    --- This DE shall be presented as specified in ETSI TS 102 894-2 [5]
    --- TurningRadius.
    turningRadius              TurningRadius,

    --- Perpendicular distance between the front wheel axle and front bumper.
    --- This DE is included in the impactReduction DF.
    --- This DE shall be presented as specified in ETSI TS 102 894-2 [5]
    --- PosFrontAx.
    posFrontAx                 PosFrontAx,

    --- This DF indicates whether a in vehicle seat is occupied at the moment
    --- when the impactReduction is generated. The in vehicle seats layout is
    --- defined in rows from the front to the rear of the vehicle. The left
    --- seat of a row refers to the left side with regards to the vehicle
    --- heading direction.   This DE is included in the impactReduction
    --- container.
    --- This DE shall be presented as specified in ETSI TS 102 894-2 [5]
    --- PositionOfOccupants.
    positionOfOccupants        PositionOfOccupants,

    --- This DE indicates the mass of an empty load vehicle. This DE is
    --- included in the impactReduction DF in the alacarte container.
    --- This DE shall be presented as specified in ETSI TS 102 894-2 [5]
    --- VehicleMass.
    vehicleMass                VehicleMass,

    --- This DE is included in impactReduction DF in the alacarte container. It
    --- indicates whether the originating ITS-S transmitting the
    --- impactReduction DF is requesting the receiving ITS-S to provide also
    --- its impactReduction DF.   On reception of a DENM with this DE set to 0,
    --- the receiving ITS-S may in turn transmit a DENM with its
    --- impactReduction DF as response to the request.
    --- In request case, this DE shall be set to 0. In response case, this DE
    --- shall be set to 1. This DE shall be presented as specified in
    --- ETSI TS 102 894-2 [5] RequestResponseIndication.
    requestResponseIndication  RequestResponseIndication
    
}

RoadWorksContainerExtended ::= SEQUENCE {

    --- This DE indicates whether a roadwork vehicle has switched on the light
    --- bar or siren. This DE is included in roadWorks DF in the alacarte
    --- container. It is used when the roadwork involves a specific roadwork
    --- vehicle.
    --- This DE is OPTIONAL. It shall be present when this information is
    --- required by the ITS application.   This DE shall be presented as
    --- specified in ETSI TS 102 894-2 [5] LightBarSirenInUse.
    lightBarSirenInUse         LightBarSirenInUse      OPTIONAL,

    --- This DF indicates whether the roadwork has caused the closure of one or
    --- several driving lanes. Optionally, the DF may indicate whether a hard
    --- shoulder lane is closed to traffic or may be used for specific usage
    --- (e.g. for stopping). This DF is included in roadWorks DF in the
    --- alacarte container.
    --- This DF is OPTIONAL. It shall be present when the information is
    --- required by the ITS application.   This DF shall be presented as
    --- specified in ETSI TS 102 894-2 [5] ClosedLanes. 
    closedLanes                ClosedLanes             OPTIONAL,

    --- This DF indicates the types of vehicles that are restricted to access
    --- the road work zone. More than one vehicle types may be provided by this
    --- DF if the restriction apply to multiple vehicle types. This DF is
    --- included in roadWorks DF in the alacarte container.
    --- This DF is OPTIONAL. It shall be present when the information is
    --- required by the ITS application. This DF shall be presented as
    --- specified in ETSI TS 102 894-2 [5] RestrictedTypes. 
    restriction                RestrictedTypes         OPTIONAL,

    --- This DE indicates the speed limitation applied to the roadwork zone.
    --- This DE is included in roadWorks DF in the alacarte container.
    --- This DE is OPTIONAL. It shall be present when the information is
    --- required by the ITS application. This DE shall be presented as
    --- specified in ETSI TS 102 894-2 [5] SpeedLimit.
    speedLimit                 SpeedLimit              OPTIONAL,

    --- This DF indicates the incident related to the roadworks to provide
    --- additional information of the roadworks zone. This DF is included in
    --- roadWorks DF in the alacarte container.
    --- This DF is OPTIONAL. It shall be present when the information is
    --- required by the ITS application. This DF shall be presented as
    --- specified in ETSI TS 102 894-2 [5] CauseCode.
    incidentIndication         CauseCode               OPTIONAL,

    --- This DF indicates the recommended itinerary in order to contour the
    --- roadworks zone. A recommended path is presented with a list of path
    --- points in the order from the starting point closest to the roadworks
    --- zone to the end point of the recommended path. This DF is included in
    --- roadWorks DF in the alacarte container.
    --- This DF is OPTIONAL. It shall be present when the information is
    --- required by the ITS application. This DF shall be presented as
    --- specified in ETSI TS 102 894-2 [5] ItineraryPath.
    recommendedPath            ItineraryPath           OPTIONAL,

    --- The DF indicates the effective starting position of a speed limit being
    --- applied to the roadwork zone. Generally speaking, the speed limit
    --- applies a certain distance prior to the roadwork zone starting
    --- position. It is described as a delta position with regards to the
    --- eventPosition for a DENM.   This DF is included in roadWorks DF in the
    --- alacarte container.
    --- This DF is OPTIONAL. It shall be present if required by the ITS
    --- application. This DF shall be presented as specified in
    --- ETSI TS 102 894-2 [5] DeltaReferencePosition.
    startingPointSpeedLimit    DeltaReferencePosition  OPTIONAL,

    --- The DE indicates the side of the road to which the traffic should flow
    --- around a roadwork.The traffic could flow to the left or to the right of
    --- the roadwork. This DE is included in roadWorks DF in the alacarte
    --- container.
    --- This DE is OPTIONAL. It shall be present if required by the ITS
    --- application. This DE shall be presented as specified in
    --- ETSI TS 102 894-2 [5] TrafficRule.
    trafficFlowRule            TrafficRule             OPTIONAL,

    --- The DF indicates is a sequence of actionIDs for different DENMs that
    --- describe the same event. If it is available it is part of all DENMs
    --- describing this event. This DF is included in roadWorks DF in the
    --- alacarte container.
    --- This DF is OPTIONAL. It shall be present if required by the ITS
    --- application. This DF consists of list of other DENMs describing the
    --- same road work event. Each DENM shall be presented as specified in
    --- ETSI TS 102 894-2 [5] ActionID. 
    referenceDenms             ReferenceDenms          OPTIONAL

}

StationaryVehicleContainer ::= SEQUENCE {

    --- This DE provides the time duration of the stationary vehicle being
    --- stationary. This DE is included in stationaryVehicle DF in the alacarte
    --- container.
    --- This DE is OPTIONAL. It shall be present when the information is
    --- required by the ITS application. This DE shall be presented as
    --- specified in ETSI TS 102 894-2 [5] StationarySince.
    stationarySince         StationarySince         OPTIONAL,

    --- This DE provides additional information to describe causes of the
    --- stationary vehicle event such as human problem as defined in
    --- ETSI TS 101 539-1 [i.4]. This DE is included in stationaryVehicle DF in
    --- the alacarte container.
    --- This DE is OPTIONAL. It shall be present when the information is
    --- required by the ITS application. This DE shall be presented as
    --- specified in ETSI TS 102 894-2 [5] CauseCode. 
    stationaryCause         CauseCode               OPTIONAL,

    --- DF included in the stationaryVehicle DF in the alacarte container if a
    --- vehicle carrying dangerous goods is involved in a stationary vehicle
    --- event. It provides information on the type of dangerous goods, the
    --- required emergency action and other information.   This DF is included
    --- in stationaryVehicle DF in the alacarte container.
    --- This DF is OPTIONAL. It shall be present when the information is
    --- required by the ITS application. This DF shall be presented as
    --- specified in ETSI TS 102 894-2 [5] DangerousGoodsExtended.
    carryingDangerousGoods  DangerousGoodsExtended  OPTIONAL,

    --- This DE provides the estimated number of occupants involved in the
    --- stationary vehicle event as specified in ETSI TS 101 539-1 [i.4]. This
    --- DE is included in stationaryVehicle DF in the alacarte container.
    --- This DE is OPTIONAL, it shall be present when the information is
    --- required by the ITS application. This DE shall be presented as
    --- specified in ETSI TS 102 894-2 [5] NumberOfOccupants.
    numberOfOccupants       NumberOfOccupants       OPTIONAL,

    --- This DF provides the vehicle identification of the stationary vehicle
    --- as specified in ETSI TS 101 539-1 [i.4], including the World
    --- Manufacturer Identifier (WMI) code and the Vehicle Descriptor Section
    --- (VDS) as defined in ISO 3779 [i.15]. This DF is included in
    --- stationaryVehicle DF in the alacarte container.
    --- This DF is OPTIONAL. It shall be present when the information is
    --- required by the ITS application. This DF shall be presented as
    --- specified in ETSI TS 102 894-2 [5] VehicleIdentification.
    vehicleIdentification   VehicleIdentification   OPTIONAL,

    --- This DE provides the vehicle energy storage type information of the
    --- stationary vehicle as specified in ETSI TS 101 539-1 [i.4], such as
    --- electric, diesel, etc. This DE is included in stationaryVehicle DF in
    --- the alacarte container.
    --- This DE is OPTIONAL. It shall be present when the information is
    --- required by the ITS application. This DE shall be presented as
    --- specified in ETSI TS 102 894-2 [5] EnergyStorageType.
    energyStorageType       EnergyStorageType       OPTIONAL

}

AlacarteContainer ::= SEQUENCE {

    --- The lane position of the event position in the road counted from the
    --- outside boarder of the road. This DE in included in the alacarte
    --- container. If this data is provided, the originating ITS-S is required
    --- to determine the lane position with a predefined confidence level as
    --- defined by the ITS applications (e.g. 95 %).
    --- This DE is OPTIONAL. It shall be present when this information is
    --- required by the ITS application. This DE shall be presented as
    --- specified in ETSI TS 102 894-2 [5] LanePosition. 
    lanePosition        LanePosition                OPTIONAL,

    --- DF included in the alacarte container of DENM to support the pre-crash
    --- use case. It contains the vehicle detailed information required for
    --- mitigating the consequences of a collision.
    --- This DF is OPTIONAL. It shall be present when this information is
    --- required by the ITS application.   This DF shall be presented as
    --- specified in Annex A.
    impactReduction     ImpactReductionContainer    OPTIONAL,

    --- Information included in the alacarte container for the adverse weather
    --- condition use case as specified in ETSI TS 101 539-1 [i.4]. It
    --- indicates the ambient temperature at the event position.
    --- This DE shall be presented as specified in ETSI TS 102 894-2 [5]
    --- Temperature.
    externalTemperature Temperature                 OPTIONAL,

    --- DF included in the alacarte container for the road work use case as
    --- specified in ETSI TS 101 539-1 [i.4].   It includes information of the
    --- road work zone and specific access conditions.
    --- This DF is OPTIONAL. It shall be present when this information is
    --- required by the ITS application.   This DF shall be presented as
    --- specified in Annex A.
    roadWorks           RoadWorksContainerExtended  OPTIONAL,

    --- This DE indicates technical solution being used by the originating
    --- ITS-S to estimate the event position. Typically, this DE may be
    --- included for events that are caused by vehicle ITS-S. This DE is
    --- included in the alacarte container.
    --- This DE is OPTIONAL, it shall be present when the information is
    --- required by the ITS application. This DE shall be presented as
    --- specified in ETSI TS 102 894-2 [5] PositioningSolutionType.
    positioningSolution PositioningSolutionType     OPTIONAL,

    --- DF included in the alacarte container for the stationary vehicle use
    --- case as specified in ETSI TS 101 539-1 [i.4]. It provides information
    --- of the stationary vehicle.
    --- This DF is OPTIONAL. It shall be present when the information is
    --- required by the ITS application. This DF shall be presented as
    --- specified in Annex A.
    stationaryVehicle   StationaryVehicleContainer  OPTIONAL,

    ...

}

defaultValidity INTEGER ::= 600 

Termination ::= ENUMERATED {
    isCancellation(0),
    isNegation (1)
} 

ReferenceDenms ::= SEQUENCE (SIZE(1..8, ...)) OF ActionID 

END
